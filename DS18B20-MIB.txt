DS18B20-MIB DEFINITIONS ::= BEGIN

IMPORTS
	OBJECT-TYPE, Integer32,
	MODULE-IDENTITY, enterprises          FROM SNMPv2-SMI
	MODULE-COMPLIANCE, OBJECT-GROUP       FROM SNMPv2-CONF;

edRixon MODULE-IDENTITY
    LAST-UPDATED "202009200000Z"
    ORGANIZATION "edrixon"
    CONTACT-INFO "postal:   Ed Rixon
		  email:    ed@ednet.pri
                 "
    DESCRIPTION  "
                  A simple mib for DS18B20.
                 "
    ::= { enterprises 56234 }

ds18b20 OBJECT IDENTIFIER ::= { edRixon 1 }

ds18b20Version OBJECT-TYPE
  SYNTAX        OCTET STRING (SIZE(2))
  MAX-ACCESS    read-only
  STATUS        current
  DESCRIPTION
    "MIB version"
  ::= { ds18b20 1 }

ds18b20sensorTable OBJECT-TYPE
  SYNTAX	SEQUENCE OF Ds18b20sensorType
  MAX-ACCESS    not-accessible
  STATUS        current
  DESCRIPTION
    "Table of sensor information"
  ::= { ds18b20 2 }

ds18b20sensorType OBJECT-TYPE
  SYNTAX        Ds18b20sensorType
  MAX-ACCESS    not-accessible
  STATUS        current
  DESCRIPTION
    "per sensor information"
  INDEX { ds18b20index }
  ::= { ds18b20sensorTable 1 }

Ds18b20sensorType ::= SEQUENCE {
  ds18b20index  Integer32,
  ds18b20addr   OCTET STRING (SIZE(8)) 
  ds18b20temp   Integer32
  }

ds18b20index OBJECT-TYPE
  SYNTAX        Integer32
  MAX-ACCESS    read-only
  STATUS        current
  DESCRIPTION
    "Index into sensor table"
  ::= { ds18b20sensorType 1 }

ds18b20addr OBJECT-TYPE
  SYNTAX        OCTET STRING (SIZE(8))
  MAX-ACCESS    read-only
  STATUS        current
  DESCRIPTION
    "Device address on 1-wire bus"
  ::= { ds18b20sensorType 2 }

ds18b20temp OBJECT-TYPE
  SYNTAX        Integer32
  MAX-ACCESS    read-only
  STATUS        current
  DESCRIPTION
    "The temperature reported by sensor multipled by 100"
  ::= { ds18b20sensorType 3 }

END
